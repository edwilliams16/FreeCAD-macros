# -*- coding: utf-8 -*-

__Version__ = '0.7.0'
__Date__ = '2022-03-03'
__License__ = 'LGPL-3.0-or-later'
__Web__ = ''
__Wiki__ = 'README.md'
__Name__ = 'Objects To Python'
__Comment__ = 'Exports objects from a FreeCAD project to a python script'
__Author__ = 'Christi'
__Icon__ = 'ObjectsToPython.svg'
__Help__ = 'ObjectsToPython/README.md'
__Status__ = 'Alpha'
__Requires__ = 'FreeCAD >= 0.19'
__Communication__ = 'https://forum.freecadweb.org/viewtopic.php?f=22&t=34612'
__Files__ = 'ObjectsToPython/README.md,ObjectsToPython/ObjectsToPython.ui,ObjectsToPython.svg'

VERSION_STRING = __Name__ + ' Macro v' + __Version__


import FreeCAD as app
import FreeCADGui as gui
import Part
import re
import sys
from FreeCAD import Vector, Placement, Rotation

               
def exportObjectsToPython(doc = app.activeDocument()):        
    addScriptFunc('from FreeCAD import Vector, Placement, Rotation')
    addScriptFunc('import Sketcher');
    addScriptFunc('import Part');
    addScriptFunc('import FreeCAD as app');
    objectlist = []
    skip_objects = [('App::Line', 'X_Axis'), ('App::Line', 'Y_Axis'), ('App::Line', 'Z_Axis'),
                   ('App::Plane', 'XY_Plane'), ('App::Plane', 'XZ_Plane'), ('App::Plane', 'YZ_Plane'),
                   ('App::Origin', 'Origin')] 
    
    selection = gui.Selection.getSelection() 
    if not selection:
        selection = doc.Objects
    else:
        expandSelection(selection)
        
    for obj in doc.Objects:  
        objectlist.append(doc.getObject(obj.Name)) 
         
    for obj in selection:    
        if obj.TypeId == 'Sketcher::SketchObject': 
            addScriptFunc('')
            addScriptFunc("def createSketch_%s(doc):"%varname(obj))
            addObject(doc, obj, objectlist)
            addScript('return ' + varname(obj))
        
    addScriptFunc('')
    addScriptFunc('')
    addScriptFunc("def make_%s():"%doc.Name)
    if not selection:
        addScript("doc = app.newDocument('%s')"%doc.Name)
    else:
        addScript('doc = app.activeDocument()')
    
    for obj in selection: 
        if (obj.TypeId, obj.Label) not in skip_objects:
            addScriptFunc('')
            if obj.TypeId == 'Sketcher::SketchObject':
                addScript(varname(obj) + " = createSketch_%s(doc)"%varname(obj))
            else:
                addObject(doc, obj, objectlist)            
                
    for obj in selection: 
        if obj.TypeId == 'PartDesign::Body':
            addScriptFunc('')
            addScript("%s.Group = %s_Group"%(varname(obj), varname(obj))) 
            if obj.Tip:
                addScript("%s.Tip = %s"%(varname(obj), varname(obj.Tip))) 
            
    #addScript('') 
    addScript('doc.recompute()') 
    addScriptFunc('')
    addScriptFunc('')
    addScriptFunc("make_%s()"%doc.Name)
        
  
def varname(obj):
    forbidden = [' ', '.', ',', '%', '+', '-', '*', '/','(',')','[',']','=','"',"'"]
    l = obj.Label
    for f in forbidden:
        l = l.replace(f, '_')
        
    if l[0].isdigit(): l = '_' + l
    return l
      
def addScript(line):
    dialog.form.textEdit.append('\t' + line)
    
def addScriptFunc(line):
    dialog.form.textEdit.append(line)
    
def expandSelection(selection):    
    addthis = []     
    for obj in selection:    
        if hasattr(obj, 'Group'):
            addthis += obj.Group
        if hasattr(obj, 'Source'):
            addthis.append(obj.Source)
        if hasattr(obj, 'Links'):
            addthis += obj.Links
            
    addcount = 0
    for a in addthis:
        if (not a in selection) and hasattr(obj, 'Name') and hasattr(obj, 'TypeId'):
            selection.insert(0, a)
            addcount = addcount + 1
            
    if addcount > 0:
        expandSelection(selection)
            

def addObject(doc, obj, objectlist): 
    objname = varname(obj)
    addScript("%s = doc.addObject('%s', '%s')"%(objname, obj.TypeId, objname))
    defaultobj = doc.addObject(obj.TypeId, obj.Name + 'Default')
    addProperties(obj, objname, defaultobj, objectlist)
    addProperties(obj.ViewObject, objname + '.ViewObject', defaultobj.ViewObject, [])                      
    doc.removeObject(obj.Name + 'Default')      
    
    
def addProperties(obj, objname, refobj, objectlist):
    skipProperties = ['Label', 'Shape', 'Proxy', 'AddSubShape', 'FullyConstrained', 'VisualLayerList']
    skipObjProp = [('Sketcher::SketchObject', 'Geometry'), ('Sketcher::SketchObject', 'Constraints'),
        ('PartDesign::Body', 'Origin'), ('PartDesign::Body', 'Tip')]
    
    if obj.TypeId == 'Spreadsheet::Sheet':
        addSpreadsheet(obj, objname)
        return
    
    if obj.TypeId == 'Sketcher::SketchObject':
        addSketch(obj, objname)

    for propname in obj.PropertiesList:
        if (not propname in skipProperties) and (not (obj.TypeId, propname) in skipObjProp):
            prop = obj.getPropertyByName(propname)  
            val = objectToText(prop, objectlist)
            
            try:
                refprop = refobj.getPropertyByName(propname)
                defaultval = objectToText(refprop, objectlist)
            except:
                defaultval = None       
                
            if propname == 'Support':
                val = val.replace('XY_Plane', 'doc.XY_Plane')
                val = val.replace('XZ_Plane', 'doc.XZ_Plane')
                val = val.replace('YZ_Plane', 'doc.YZ_Plane')
                
            if propname == 'ExpressionEngine':
                for expression in prop:
                    addScript(objname + ".setExpression" + str(expression).replace('<', '').replace('>',''))

            elif propname == '_Body':
                addScript("%s_Group.append(%s)"%(val, objname))
                          
            elif (obj.TypeId, propname) == ('PartDesign::Body', 'Group'):
                addScript("%s_Group = []"%(objname))
                                                
            elif (obj.TypeId, propname) == ('App::Part', 'Group'):
                proplist = []
                for pn in prop:
                    proplist.append(varname(pn))
                    
                addScript(objname + '.Group = ' + str(proplist))
                                                     
            elif objectToText(prop, objectlist) is not None:   
                if val != defaultval:        
                    addScript("%s.%s = %s"%(objname, propname, val))   
                                      
                                                                                                                            
def objectToText(obj, objectlist = []):    
    if obj in objectlist:
        return obj.Label
    
    else:
        if hasattr(obj, 'Value') and hasattr(obj, 'Unit'):  # how can I test if type(obj) is Base.Quantity ?
            return str(obj.Value)
        else:     
            if isinstance(obj, str):
                return "'" + str(obj) + "'"
                
            if isinstance(obj, bool):
                if obj:
                    return 'True'
                else:
                    return 'False'
            
            if isinstance(obj, int):
                return str(obj)
    
            if isinstance(obj, float):
                return floatstr(obj)                                      
            
            if isinstance(obj, Placement):
                return "Placement(%s, %s)"%(objectToText(obj.Base), objectToText(obj.Rotation))
            
            if isinstance(obj, Part.Point):
                return "Part.Point(Vector(%s, %s, %s))"%(floatstr(obj.X), floatstr(obj.Y), floatstr(obj.Z))
            
            if isinstance(obj, Part.LineSegment):
                return "Part.LineSegment(%s, %s)"%(obj.StartPoint, obj.EndPoint)
            
            if isinstance(obj, Part.Circle):
                return "Part.Circle(%s, %s, %s)"%(vecstr(obj.Center), obj.Axis, floatstr(obj.Radius))
            
            if isinstance(obj, Part.ArcOfCircle):
                #return "Part.ArcOfCircle(%s, %s, %s)"%(obj.Center, obj.StartPoint, obj.EndPoint)
                return "Part.ArcOfCircle(%s, %s, %s)"%(objectToText(obj.Circle), obj.FirstParameter, obj.LastParameter)
            
            if isinstance(obj, Part.Ellipse):
                return "Part.Ellipse(%s, %s, %s)"%(vecstr(obj.Center), obj.MajorRadius, obj.MinorRadius)
            
            if isinstance(obj, Part.BSplineCurve):
                poles = obj.getPoles().__repr__()
                mults = obj.getMultiplicities().__repr__()
                knots =  obj.getKnots().__repr__()
                periodic = obj.isPeriodic().__repr__()
                degree =  obj.Degree.__repr__()
                weights = obj.getWeights().__repr__()
                CheckRational = obj.isRational().__repr__()
                return f'Part.BSplineCurve({poles}, mults = {mults}, knots = {knots}, periodic = {periodic}, degree = {degree}, weights = {weights}, CheckRational = {CheckRational})'
                            
            if isinstance(obj, Part.Parabola):
                return "Part.Parabola(%s, %s, %s)"%(vecstr(obj.Focus), vecstr(obj.Location), vecstr(obj.Axis))
                
            if isinstance(obj, Part.Hyperbola):
                return "Part.Hyperbola(%s, %s, %s)"%(vecstr(obj.Center), obj.MajorRadius, obj.MinorRadius)
                
            if isinstance(obj, Part.ArcOfEllipse):
                return "Part.ArcOfEllipse(%s, %s, %s)"%(objectToText(obj.Ellipse), obj.FirstParameter, obj.LastParameter)
            
            if isinstance(obj, Part.ArcOfParabola):
                return "Part.ArcOfParabola(%s, %s, %s)"%(objectToText(obj.Parabola), obj.FirstParameter, obj.LastParameter)
                
            if isinstance(obj, Part.ArcOfHyperbola):
                return "Part.ArcOfHyperbola(%s, %s, %s)"%(objectToText(obj.Hyperbola), obj.FirstParameter, obj.LastParameter)
            
            if isinstance(obj, Vector):
                return vecstr(obj)

            liststart = ''
            if isinstance(obj, list):
                liststart = '['
                listend = ']'
                
            if isinstance(obj, tuple):
                liststart = '('
                listend = ')'
                
            if liststart != '':
                sline = liststart;
                comma = False
                for listele in obj:
                    if comma:
                        sline = sline + ', '
                    else:
                        comma = True                
                
                    val = objectToText(listele, objectlist)
                    if val is not None:
                        sline = sline + val
                    
                sline += listend;
                return sline                  
            
            stringobj = str(obj)                           
            return stringobj
        
    
def addSketch(obj, objname): 
    prop = obj.getPropertyByName('Geometry')
    gflist = obj.GeometryFacadeList
 
    n = 0
    exposing = 0
    exposed = []
    for geo in prop:
        objstr = objectToText(geo)
        
        if exposing > 0:
            exposed.append(n)
            exposing = exposing - 1
        else:
            addScript("geo%d = %s.addGeometry(%s)"%(n, objname, objstr))           
            if gflist[n].Construction:
                addScript("%s.toggleConstruction(geo%d)"%(objname, n))
                        
            if isinstance(geo, Part.BSplineCurve):
                poles = len(geo.getPoles())
                exposing = poles - 2
                if exposing < 2: exposing = 2
                
            if isinstance(geo, Part.ArcOfParabola):
                exposing = 2
                
            if isinstance(geo, Part.ArcOfHyperbola):
                exposing = 3
                
            if isinstance(geo, Part.ArcOfEllipse):
                exposing = 4
                
            if exposing > 0:
                addScript("%s.exposeInternalGeometry(geo%d)"%(objname, n))                
                
        n = n + 1
    
    splinecount = 0
    concount = 0
    prop = obj.getPropertyByName('Constraints')
    for con in obj.Constraints:
        conargs = con.Value
        contype = con.Type
        if con.First < 0:
            first = str(con.First)
        else:
            first = "geo%d"%(con.First)
        
        if con.Second < 0:
            sec = str(con.Second)
        else:
            sec = "geo%d"%(con.Second)
            
        if con.Third < 0:
            third = str(con.Third)
        else:
            third = "geo%d"%(con.Third)

        if con.Type == 'Coincident':
            conargs = "%s, %d, %s, %d"%(first, con.FirstPos, sec, con.SecondPos)
        
        elif con.Type == 'PointOnObject':
            conargs = "%s, %d, %s"%(first, con.FirstPos, sec)
        
        elif con.Type == 'Vertical':
            if con.Second == -2000:
                conargs = str(first) #line
            else:
                conargs = "%s, %d, %s, %d"%(first, con.FirstPos, sec, con.SecondPos) #two points
        
        elif con.Type == 'Horizontal':
            if con.Second == -2000:
                conargs = str(first)
            else:
                conargs = "%s, %d, %s, %d"%(first, con.FirstPos, sec, con.SecondPos)
        
        elif con.Type == 'Parallel':
            conargs = "%s, %s"%(first, sec)
        
        elif con.Type == 'Perpendicular':
            if con.FirstPos == 0:
                conargs = "%s, %s"%(first, sec)
            elif con.SecondPos ==0:
                conargs = "%s, %d, %s"%(first, con.FirstPos, sec)
            else:
                conargs = "%s, %d, %s, %d"%(first, con.FirstPos, sec, con.SecondPos)
        
        elif con.Type == 'PerpendicularViaPoint':
            conargs = "%s, %s, %s, %d"%(first, sec, third, con.ThirdPos)
        
        elif con.Type == 'Tangent':
            if con.Second < 0:
                conargs = "%s, %d"%(first, con.FirstPos)
            elif con.SecondPos == 0:
                conargs = "%s, %d, %s"%(first, con.FirstPos, sec)
            else:
                conargs = "%s, %d, %s, %d"%(first, con.FirstPos, sec, con.SecondPos)
        
        elif con.Type == 'TangentViaPoint':
            conargs = "%s, %s, %s, %d"%(first, sec, third, con.ThirdPos)
        
        elif con.Type == 'Equal':
            conargs = "%s, %s"%(first, sec)
        
        elif con.Type == 'Symmetric':
            if con.ThirdPos == 0:
                conargs = "%s, %d, %s, %d, %s"%(first, con.FirstPos, sec, con.SecondPos, third)
            else:
                conargs = "%s, %d, %s, %d, %s, %d"%(first, con.FirstPos, sec, con.SecondPos, third, con.ThirdPos)
        
        elif con.Type == 'Block':
            conargs = str(first)
        
        elif con.Type == 'Distance':
            if con.Second == -2000:
                conargs = "%s, %s"%(first, floatstr(con.Value))
            elif con.FirstPos == 0:
                conargs = "%s, %s, %s"%(first, sec, floatstr(con.Value))
            elif con.SecondPos == 0:
                conargs = "%s, %d, %s, %s"%(first, con.FirstPos, sec, floatstr(con.Value))
            else:
                conargs = "%s, %d, %s, %d, %s"%(first, con.FirstPos, sec, con.SecondPos, floatstr(con.Value))
        
        elif con.Type == 'DistanceX' or con.Type == 'DistanceY':
            if con.Second == -2000:
                conargs = "%s, %d, %s"%(first, con.FirstPos, floatstr(con.Value))
            else:
                conargs = "%s, %d, %s, %d, %s"%(first, con.FirstPos, sec, con.SecondPos, floatstr(con.Value))
        
        elif con.Type == 'Angle':
            if con.FirstPos == 0:
                conargs = "%s, %s, %s"%(first, sec, floatstr(con.Value))
            else:
                conargs = "%s, %d, %s, %d, %s"%(first, con.FirstPos, sec, con.SecondPos, floatstr(con.Value))
        
        elif con.Type == 'AngleViaPoint':
            conargs = "%s, %s, %s, %s"%(first, sec, third, floatstr(con.Value))
        
        elif con.Type == 'Weight' or con.Type == 'Radius' or con.Type == 'Diameter':
            conargs = "%s, %s"%(first, floatstr(con.Value))
            splinecount = 0
        
        elif con.Type == 'InternalAlignment':
            if con.Second > con.First:
                contype = 'InternalAlignment:Sketcher::BSplineControlPoint'
                conargs = "%s, %d, %s, %d"%(first, con.FirstPos, sec, splinecount)
                splineindex = con.Second
                splinecount = splinecount + 1
            else:
                conargs = None
        
        elif con.Type == 'Weight':
            conargs = "%s, %s"%(first, floatstr(con.Value))

        if conargs is not None:
            addScript("%s.addConstraint(Sketcher.Constraint('%s', %s))"%(objname, contype, conargs))
            
        if con.Name != "":
            addScript("%s.renameConstraint(%d, u'%s')"%(objname, concount, con.Name))
    
        concount = concount + 1
                                 
def addSpreadsheet(obj, objname): 
    for propname in obj.PropertiesList:    
        match = re.search('[A-Z]+[0-9]+', propname)
        if match:
            prop = obj.getPropertyByName(propname)
            val = objectToText(prop)
            addScript("%s.set('%s', '%s')"%(objname, propname, val.replace("'", '')))  
            alias = obj.getAlias(propname)
            if alias is not None:
                addScript("%s.setAlias('%s', '%s')"%(objname, propname, alias))
    
    addScript('doc.recompute()')   
      
def floatstr(f):
    #return '{:.2f}'.format(f)
    return str(f)
     
def vecstr(v):
    return 'Vector(' + floatstr(v.x) + ', ' + floatstr(v.y) + ', ' + floatstr(v.z) + ')'

class O2PDialog:
    """Show a dialog for BoxCreator"""
    def __init__(self):
        self.ui_file = os.path.join(app.getUserMacroDir(True), 'ObjectsToPython/ObjectsToPython.ui')
        self.form = gui.PySideUic.loadUi(self.ui_file)
        self.form.pushButtonClose.pressed.connect(self.form_Close)
        self.form.show()    

    def form_Close(self):
	    self.form.close()
  
dialog = O2PDialog()     
exportObjectsToPython()
